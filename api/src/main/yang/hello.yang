module hello {
    yang-version 1;
    namespace "urn:opendaylight:params:xml:ns:yang:hello";
    prefix "hello";

    revision "2015-01-05" {
        description "Initial revision of hello model";
    }
    rpc hello-world {
        input {
            leaf name {
                type string;
            }
        }
        output {
            leaf greeting {
                type string;
            }
        }
    }
    container greeting-registry {
        list greeting-registry-entry {
            key "name";
            leaf name{
                type string;
            }
            leaf greeting{
                type string;
            }
        }
    }
}
